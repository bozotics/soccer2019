/*
 *   Title : addHole.ulp
 * Version : 0.1 alpha 1
 *    Date : 28-Feb-2017
 *  Author : Rachael Peterson
 *
 * Purpose : Provide the ability to add either plated or non-plated holes based
 *         : on arcs and circles already defined on the PCB, for example from a
 *         : mechanical drawing imported into EAGLE from a DXF file.
 *
 * License : Creative Commons Attribution-ShareAlike 4.0 International
 *         : CC BY-SA 4.0
 *         : https://creativecommons.org/licenses/by-sa/4.0/
 *
 *******************************************************************************
 *                           (c)Copyright 2017                                 *
 *******************************************************************************
 * THIS SOFTWARE IS PROVIDED BY THE AUTHOR ``AS IS'' AND ANY EXPRESS OR IMPLIED
 * WARRANTIES, INCLUDING, BUT NOT LIMITED TO, THE IMPLIED WARRANTIES OF
 * MERCHANTABILITY AND FITNESS FOR A PARTICULAR PURPOSE ARE DISCLAIMED. IN NO
 * EVENT SHALL THE AUTHOR BE LIABLE FOR ANY DIRECT, INDIRECT, INCIDENTAL,
 * SPECIAL, EXEMPLARY, OR CONSEQUENTIAL DAMAGES (INCLUDING, BUT NOT LIMITED TO,
 * PROCUREMENT OF SUBSTITUTE GOODS OR SERVICES; LOSS OF USE, DATA, OR PROFITS;
 * OR BUSINESS INTERRUPTION) HOWEVER CAUSED AND ON ANY THEORY OF LIABILITY,
 * WHETHER IN CONTRACT, STRICT LIABILITY, OR TORT (INCLUDING NEGLIGENCE OR
 * OTHERWISE) ARISING IN ANY WAY OUT OF THE USE OF THIS SOFTWARE, EVEN IF
 * ADVISED OF THE POSSIBILITY OF SUCH DAMAGE.
 *
 */

#usage "en: Provides tools to enable planted and non-plated holes to be added from the context menus.\n"
       "run addHole --install - Installs the utility to the board context menus.\n"
       "run addHole --version - Shows the version number of the ULP being called.\n"
       "run addHole --locate-ulp - Shows the location of the ULP being called (Useful for debug).\n"

string VERSION = "0.1 alpha 1 (28-Feb-2017 21:33)";

if (argv[1] == "--install") {
   exit("edit .brd; set context wire 'Place hole (Non-PT)...' 'run addHole';"
        "           set context wire 'Place hole (PT)...' 'run addHole plated';"
        "           set context circle 'Place hole (Non-PT)...' 'run addHole';"
        "           set context circle 'Place hole (PT)...' 'run addHole plated';");
} else if (argv[1] == "--version"){
   string tmp = "ULP Version: " + VERSION;
   dlgMessageBox(tmp);
   exit(0);
} else if (argv[1] == "--locate-ulp"){
   dlgMessageBox(argv[0]);
   exit(0);
} else if (board) {

   string cmd="";
   string grid="mil";

   board(B) {
      if (B.grid.unit == GRID_UNIT_MIC) {
         grid = "mic";
      } else if (B.grid.unit == GRID_UNIT_MM) {
         grid = "mm";
      } else if (B.grid.unit == GRID_UNIT_INCH) {
         grid = "in";
      }
      B.wires(W) {
         if (ingroup(W)) {
            if (W.arc) {
               if (argv[1] == "plated") {
                  sprintf(cmd, "GRID mil; VIA %f Round 1-16 (%f %f); CHA DRI %f (%f %f); GRID %s;", 2.0 * u2mil(W.arc.radius), u2mil(W.arc.xc), u2mil(W.arc.yc), 2.0 * u2mil(W.arc.radius), u2mil(W.arc.xc), u2mil(W.arc.yc), grid);
               } else {
                  sprintf(cmd, "GRID mil; HOLE %f (%f %f); GRID %s;", 2.0 * u2mil(W.arc.radius), u2mil(W.arc.xc), u2mil(W.arc.yc), grid);
               }
            }
         }
      }
      B.circles(C) {
         if (ingroup(C)) {
            if (argv[1] == "plated") {
               sprintf(cmd, "GRID mil; VIA %f Round 1-16 (%f %f); CHA DRI %f (%f %f); GRID %s;", 2.0 * u2mil(C.radius), u2mil(C.x), u2mil(C.y), 2.0 * u2mil(C.radius), u2mil(C.x), u2mil(C.y), grid);
            } else {
               sprintf(cmd, "GRID mil; HOLE %f (%f %f); GRID %s;", 2.0 * u2mil(C.radius), u2mil(C.x), u2mil(C.y), grid);
            }
         }
      }
   }

   exit(cmd);

} else {
   dlgMessageBox(":ERROR: This utility is for use from within the board editor only.");
   exit(0);
}
